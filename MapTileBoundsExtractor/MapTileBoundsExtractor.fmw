FME workspace MapTileBoundsExtractor.fmw

Parameters:
- INPUT_FILES =   # Source GeoTIFF File(s)
- OUTPUT_FOLDER =   # Destination CSV (Comma Separated Value) Folder

Readers:
- GEOTIFF_1: GEOTIFF from $(INPUT_FILES)

Writers:
- CSV2_1: CSV2 to $(OUTPUT_FOLDER)

GEOTIFF (reader GEOTIFF_1)
    -> BoundsExtractor
BoundsExtractor
    XMAX = _xmax
    XMIN = _xmin
    YMAX = _ymax
    YMIN = _ymin
    ZMAX = _zmax
    ZMIN = _zmin
    -> AttributeManager
AttributeManager
    ATTR_TABLE:
      RENAME_SET_VALUE fme_basename > filename
      REMOVE _xmax
      RENAME_SET_VALUE _xmin > xmin
      REMOVE _ymax
      RENAME_SET_VALUE _ymin > ymin
      REMOVE _zmax
      REMOVE _zmin
    -> TileCoordinates (writer CSV2_1)
TileCoordinates (writer CSV2_1)
    attributes: filename string, xmin string, ymin string
